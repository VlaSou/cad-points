;;; CadPoints runtime smoke test for AutoCAD LT.
;;; Usage:
;;;   APPLOAD Contents/LISP/cadpoints.lsp
;;;   APPLOAD Contents/Test/cadpoints_runtime_smoke_test.lsp
;;;   Optional:
;;;     (setq *cadpoints-runtime-result-path* "C:/temp/cadpoints-runtime-result.txt")
;;;     (setq *cadpoints-runtime-csv-path* "C:/temp/cadpoints-runtime-export.csv")
;;;   Run:
;;;     CPFULLSMOKE

(defun cp-test:delete-layer-entities (layer / ss index entity)
  (setq ss (ssget "_X" (list (cons 8 layer))))
  (if ss
    (progn
      (setq index 0)
      (while (< index (sslength ss))
        (setq entity (ssname ss index))
        (entdel entity)
        (setq index (+ index 1))
      )
    )
  )
)

(defun cp-test:create-example-input ()
  (foreach layer '("CP_POINTS_A" "CP_POINTS_B" "CADPOINTS_POINTS" "CADPOINTS_POINT_LABELS" "CADPOINTS_TABLE" "CADPOINTS_CONTOURS")
    (cp-test:delete-layer-entities layer)
    (cp:ensure-layer layer)
  )
  (entmake
    (list
      '(0 . "LINE")
      '(100 . "AcDbEntity")
      '(8 . "CP_POINTS_A")
      '(100 . "AcDbLine")
      '(10 1000.0 2000.0 10.0)
      '(11 2000.0 2000.0 20.0)
    )
  )
  (entmake
    (list
      '(0 . "LWPOLYLINE")
      '(100 . "AcDbEntity")
      '(8 . "CP_POINTS_B")
      '(100 . "AcDbPolyline")
      '(90 . 3)
      '(70 . 0)
      '(38 . 30.0)
      '(10 3000.0 1000.0)
      '(10 4000.0 1000.0)
      '(10 4000.0 2000.0)
    )
  )
)

(defun cp-test:write-line (file value)
  (write-line value file)
)

(defun cp-test:pass (label)
  (setq *cp-test-results* (cons (strcat "PASS " label) *cp-test-results*))
)

(defun cp-test:fail (label detail)
  (setq *cp-test-results* (cons (strcat "FAIL " label ": " detail) *cp-test-results*))
)

(defun cp-test:check (label condition detail)
  (if condition
    (cp-test:pass label)
    (cp-test:fail label detail)
  )
)

(defun cp-test:command-defined-p (command-name)
  (member (strcase command-name) (atoms-family 1))
)

(defun cp-test:count-entities (layer entity-type / ss filter)
  (setq filter (list (cons 8 layer)))
  (if entity-type
    (setq filter (cons (cons 0 entity-type) filter))
  )
  (setq ss (ssget "_X" filter))
  (if ss (sslength ss) 0)
)

(defun cp-test:has-prefix-p (records prefix / found record name)
  (setq found nil)
  (foreach record records
    (setq name (cp:record-value "POINT_NAME" record))
    (if (and name (>= (strlen name) (strlen prefix)) (= (substr name 1 (strlen prefix)) prefix))
      (setq found T)
    )
  )
  found
)

(defun cp-test:read-lines (path / file line lines)
  (setq lines '())
  (setq file (open path "r"))
  (if file
    (progn
      (while (setq line (read-line file))
        (setq lines (cons line lines))
      )
      (close file)
    )
  )
  (reverse lines)
)

(defun cp-test:lines-equal-p (left right / ok)
  (setq ok T)
  (if (/= (length left) (length right))
    (setq ok nil)
  )
  (while (and ok left right)
    (if (/= (car left) (car right))
      (setq ok nil)
    )
    (setq left (cdr left))
    (setq right (cdr right))
  )
  ok
)

(defun cp-test:sorted-tail (lines)
  (vl-sort (cdr lines) '<)
)

(defun cp-test:csv-lines-match-p (actual expected)
  (and
    actual
    expected
    (= (car actual) (car expected))
    (cp-test:lines-equal-p (cp-test:sorted-tail actual) (cp-test:sorted-tail expected))
  )
)

(defun cp-test:collect-records (/ settings layers precision columns drawing-scale point-name-pattern draw-point-p point-layer label-p label-paper-height label-height label-layer draw-table-p table-scale table-offset-paper table-offset table-text-paper-height table-text-height table-layer draw-contours-p contour-interval contour-layer contour-splines-p sample-curves-p curve-sample-interval ss index entity entity-data entity-type layer handle point-no records segments result contour-count)
  (cp:setenv-value "LAYERS" "CP_POINTS_A,CP_POINTS_B")
  (cp:setenv-value "PRECISION" "3")
  (cp:setenv-value "COLUMNS" (cp:default-columns))
  (cp:setenv-value "DRAWING_SCALE" "100")
  (cp:setenv-value "POINT_NAME_PATTERN" "")
  (cp:setenv-value "DRAW_POINTS" "1")
  (cp:setenv-value "POINT_LAYER" "CADPOINTS_POINTS")
  (cp:setenv-value "LABELS" "1")
  (cp:setenv-value "LABEL_PAPER_HEIGHT" "2.5")
  (cp:setenv-value "LABEL_LAYER" "CADPOINTS_POINT_LABELS")
  (cp:setenv-value "DRAW_TABLE" "1")
  (cp:setenv-value "TABLE_SCALE" "100")
  (cp:setenv-value "TABLE_OFFSET_PAPER" "50")
  (cp:setenv-value "TABLE_TEXT_PAPER_HEIGHT" "2.5")
  (cp:setenv-value "TABLE_LAYER" "CADPOINTS_TABLE")
  (cp:setenv-value "DRAW_CONTOURS" "0")
  (cp:setenv-value "CONTOUR_INTERVAL" "1000")
  (cp:setenv-value "CONTOUR_LAYER" "CADPOINTS_CONTOURS")
  (cp:setenv-value "CONTOUR_SPLINES" "1")
  (cp:setenv-value "SAMPLE_CURVES" "0")
  (cp:setenv-value "CURVE_SAMPLE_INTERVAL" "1000")

  (setq settings (cp:settings-list))
  (setq layers (cp:split (cdr (assoc "LAYERS" settings)) ","))
  (setq precision (atoi (cdr (assoc "PRECISION" settings))))
  (setq columns (cp:parse-columns (cdr (assoc "COLUMNS" settings))))
  (setq drawing-scale (atof (cdr (assoc "DRAWING_SCALE" settings))))
  (setq point-name-pattern (cdr (assoc "POINT_NAME_PATTERN" settings)))
  (setq *cadpoints-point-name-pattern* point-name-pattern)
  (setq *cadpoints-point-name-counters* nil)
  (setq draw-point-p (cp:yes-value-p (cdr (assoc "DRAW_POINTS" settings))))
  (setq point-layer (cdr (assoc "POINT_LAYER" settings)))
  (setq label-p (cp:yes-value-p (cdr (assoc "LABELS" settings))))
  (setq label-paper-height (atof (cdr (assoc "LABEL_PAPER_HEIGHT" settings))))
  (setq label-height (* label-paper-height drawing-scale))
  (setq label-layer (cdr (assoc "LABEL_LAYER" settings)))
  (setq draw-table-p (cp:yes-value-p (cdr (assoc "DRAW_TABLE" settings))))
  (setq table-scale (atof (cdr (assoc "TABLE_SCALE" settings))))
  (setq table-offset-paper (atof (cdr (assoc "TABLE_OFFSET_PAPER" settings))))
  (setq table-offset (* table-offset-paper table-scale))
  (setq table-text-paper-height (atof (cdr (assoc "TABLE_TEXT_PAPER_HEIGHT" settings))))
  (setq table-text-height (* table-text-paper-height table-scale))
  (setq table-layer (cdr (assoc "TABLE_LAYER" settings)))
  (setq draw-contours-p (cp:yes-value-p (cdr (assoc "DRAW_CONTOURS" settings))))
  (setq contour-interval (atof (cdr (assoc "CONTOUR_INTERVAL" settings))))
  (setq contour-layer (cdr (assoc "CONTOUR_LAYER" settings)))
  (setq contour-splines-p (cp:yes-value-p (cdr (assoc "CONTOUR_SPLINES" settings))))
  (setq sample-curves-p (cp:yes-value-p (cdr (assoc "SAMPLE_CURVES" settings))))
  (setq curve-sample-interval (atof (cdr (assoc "CURVE_SAMPLE_INTERVAL" settings))))

  (setq ss (ssget "_X" '((0 . "LINE,LWPOLYLINE,POLYLINE,ARC,CIRCLE,ELLIPSE,SPLINE"))))
  (setq point-no 1)
  (setq records '())
  (setq segments '())

  (if ss
    (progn
      (setq index 0)
      (while (< index (sslength ss))
        (setq entity (ssname ss index))
        (setq entity-data (entget entity))
        (setq entity-type (cdr (assoc 0 entity-data)))
        (setq layer (cdr (assoc 8 entity-data)))
        (setq handle (cdr (assoc 5 entity-data)))
        (if (member layer layers)
          (progn
            (cond
              ((= entity-type "LINE")
                (setq result (cp:collect-line records segments point-no entity-data layer entity-type handle draw-point-p point-layer label-p label-height label-layer))
              )
              ((= entity-type "LWPOLYLINE")
                (if (and sample-curves-p (cp:lwpolyline-has-bulge-p entity-data))
                  (setq result (cp:collect-sampled-curve records segments point-no entity entity-data layer entity-type handle curve-sample-interval draw-point-p point-layer label-p label-height label-layer))
                  (setq result (cp:collect-lwpolyline records segments point-no entity-data layer entity-type handle draw-point-p point-layer label-p label-height label-layer))
                )
              )
              ((= entity-type "POLYLINE")
                (if (and sample-curves-p (cp:polyline-curve-like-p entity-data))
                  (setq result (cp:collect-sampled-curve records segments point-no entity entity-data layer entity-type handle curve-sample-interval draw-point-p point-layer label-p label-height label-layer))
                  (setq result (cp:collect-polyline records segments point-no entity layer entity-type handle draw-point-p point-layer label-p label-height label-layer))
                )
              )
              ((member entity-type '("ARC" "CIRCLE" "ELLIPSE" "SPLINE"))
                (if sample-curves-p
                  (setq result (cp:collect-sampled-curve records segments point-no entity entity-data layer entity-type handle curve-sample-interval draw-point-p point-layer label-p label-height label-layer))
                  (setq result (list records segments point-no))
                )
              )
            )
            (setq records (car result))
            (setq segments (cadr result))
            (setq point-no (caddr result))
          )
        )
        (setq index (+ index 1))
      )
    )
  )

  (setq records (reverse records))
  (setq segments (reverse segments))
  (if (and *cadpoints-runtime-csv-path* records)
    (cp:write-csv *cadpoints-runtime-csv-path* records columns precision)
  )
  (if (and draw-table-p records columns)
    (cp:draw-table-right records columns precision table-offset table-text-height table-layer)
  )
  (if (and draw-contours-p records segments)
    (setq contour-count (cp:draw-contours records segments contour-interval contour-layer contour-splines-p))
    (setq contour-count 0)
  )
  (list records segments contour-count)
)

(defun c:CPFULLSMOKE (/ result-path csv-path expected-path collected records contour-count file point-count label-count table-count csv-file expected-file actual-lines expected-lines)
  (setq *cp-test-results* '())
  (setq result-path (if *cadpoints-runtime-result-path* *cadpoints-runtime-result-path* "cadpoints-runtime-result.txt"))
  (setq csv-path (if *cadpoints-runtime-csv-path* *cadpoints-runtime-csv-path* "cadpoints-runtime-export.csv"))
  (setq expected-path (if *cadpoints-runtime-expected-csv-path* *cadpoints-runtime-expected-csv-path* "expected_output.csv"))
  (setq *cadpoints-runtime-csv-path* csv-path)
  (cp-test:create-example-input)

  (cp-test:check "command CPHELP defined" (cp-test:command-defined-p "C:CPHELP") "c:CPHELP is not defined")
  (cp-test:check "command CPSETTINGS defined" (cp-test:command-defined-p "C:CPSETTINGS") "c:CPSETTINGS is not defined")
  (cp-test:check "command CPEXPORT defined" (cp-test:command-defined-p "C:CPEXPORT") "c:CPEXPORT is not defined")
  (cp-test:check "source layer CP_POINTS_A exists" (tblsearch "LAYER" "CP_POINTS_A") "missing CP_POINTS_A")
  (cp-test:check "source layer CP_POINTS_B exists" (tblsearch "LAYER" "CP_POINTS_B") "missing CP_POINTS_B")

  (setq collected (cp-test:collect-records))
  (setq records (car collected))
  (setq contour-count (caddr collected))
  (setq point-count (cp-test:count-entities "CADPOINTS_POINTS" "POINT"))
  (setq label-count (cp-test:count-entities "CADPOINTS_POINT_LABELS" "TEXT"))
  (setq table-count (cp-test:count-entities "CADPOINTS_TABLE" nil))
  (setq csv-file (findfile csv-path))
  (setq expected-file (findfile expected-path))

  (cp-test:check "records exported" (> (length records) 0) "no point records were collected")
  (cp-test:check "expected record count" (= (length records) 5) (strcat "record count " (itoa (length records))))
  (cp-test:check "CSV created" csv-file (strcat "missing CSV " csv-path))
  (cp-test:check "expected CSV fixture exists" expected-file (strcat "missing expected CSV " expected-path))
  (if (and csv-file expected-file)
    (progn
      (setq actual-lines (cp-test:read-lines csv-file))
      (setq expected-lines (cp-test:read-lines expected-file))
      (cp-test:check "CSV matches expected output" (cp-test:csv-lines-match-p actual-lines expected-lines) "actual CSV differs from expected_output.csv")
    )
  )
  (cp-test:check "point entities created" (>= point-count (length records)) (strcat "point count " (itoa point-count) ", records " (itoa (length records))))
  (cp-test:check "point labels created" (>= label-count (length records)) (strcat "label count " (itoa label-count) ", records " (itoa (length records))))
  (cp-test:check "table entities created" (> table-count 0) "no table entities on CADPOINTS_TABLE")
  (cp-test:check "A prefix present" (cp-test:has-prefix-p records "A") "no A-prefixed point name")
  (cp-test:check "B prefix present" (cp-test:has-prefix-p records "B") "no B-prefixed point name")
  (cp-test:check "contour command path exercised" (>= contour-count 0) "contour generation returned invalid count")

  (setq file (open result-path "w"))
  (cp-test:write-line file "CadPoints runtime smoke test")
  (cp-test:write-line file (strcat "records=" (itoa (length records))))
  (cp-test:write-line file (strcat "points=" (itoa point-count)))
  (cp-test:write-line file (strcat "labels=" (itoa label-count)))
  (cp-test:write-line file (strcat "table_entities=" (itoa table-count)))
  (cp-test:write-line file (strcat "contours=" (itoa contour-count)))
  (cp-test:write-line file (strcat "csv=" csv-path))
  (cp-test:write-line file (strcat "expected_csv=" expected-path))
  (foreach item (reverse *cp-test-results*)
    (cp-test:write-line file item)
  )
  (close file)
  (princ (strcat "\nCPFULLSMOKE wrote " result-path))
  (princ)
)
